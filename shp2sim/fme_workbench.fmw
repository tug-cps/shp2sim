FME workspace fme_workbench.fmw

Parameters:
- DestDataset_CITYGML = $(FME_MF_DIR)gmlout1.gml   # Destination CityGML Document
- SourceDataset_SHAPEFILE = C:\Users\there\Desktop\TU Graz\shpfile_campus\campus_inffeld_basis.shp   # Source Esri Shapefile(s)

Readers:
- SHAPEFILE_1: SHAPEFILE from $(SourceDataset_SHAPEFILE)

Writers:
- CITYGML_1: CITYGML to $(DestDataset_CITYGML)

GeometryCoercer
    GQUERY:
      for $geom in //geometry
      where $geom/count(parent::geometry) = 0
      return number($geom/@fme_id)
    KIND = fme_brep_solid
    COERCED -> GeometryValidator
GeometryValidator
    PRESETS = Custom
    REPAIR = Yes
    RULES = "MISSING_VERTEX_NORMALS "
    SUMMARY = None
    REPAIRED -> GeometryPropertySetter
GeometryPropertySetter
    CNT_ATTR = _count
    DOMAIN = counter
    GQUERY:
      for $geom in //geometry
      where $geom/@fme_geometry_type = 'IFMEFace'
      return number($geom/@fme_id)
    OVERWRITE_CHOICE = Yes
    SCOPE = Global
    SETTYPE_PARAM = Traits From Counter
    START = 0
    SET -> GeometryPartExtractor_3
GeometryPartExtractor_3
    GQUERY:
      for $geom in //geometry
      where $geom/@fme_geometry_type = 'IFMEFace'
      return number($geom/@fme_id)
    EXTRACTED -> GeometryValidator_2
GeometryValidator_2
    ISSUE_ATTR_NAME = _issues
    PRESETS = Custom
    REPAIR = Yes
    RULES = TYPE_REPAIR CONNECT_Z_MODE]FIRST_WINS]ARC_ENDPOINT_TOLERANCE_MODE]Auto]ARC_ENDPOINT_TOLERANCE]0.0]FME_CONTROLLER_QUERY_FILE]transformers/dependencies/geometryvalidator/TYPE_REPAIR.fme
    SUMMARY = Detailed
    PASSED -> GeometryPropertyExtractor
    REPAIRED -> GeometryPropertyExtractor
Note: for buildings who are being dissolved, but into several different building parts, it hast to be filtered by building id and then put into separate dissolvers - otherwise all building parts are dissolved into one / dissolving collectively and then deaggregating only works for buildings who do not share a boundary
GeometryPropertyExtractor
    EXTRACTTYPE_PARAM = Traits
    PREFIX_EXTRACTED_TRAITS = No
    TRAIT_ATTR_LIST = _count,No
    EXTRACTED -> GeometryPartExtractor_4
GeometryPartExtractor_4
    GQUERY:
      for $geom in //geometry
      where $geom/@fme_geometry_type = 'IFMEPolygon'
      return number($geom/@fme_id)
    EXTRACTED -> MeasureExtractor
MeasureExtractor
    GEOM_TYPE = Individual Vertex by Index
    INDEX = 0
    MEASURE_ATTR = _normal_z
    MEASURE_NAME = fme_vertex_normal_z
    -> TestFilter
TestFilter
    DEFAULT_VALUE = Wall
    TEST_LIST = "BOOL_OP,OR,COMPOSITE_TEST,""""""1"""""",TEST_CLAUSE,TEST @Value(_normal_z) < 0",Ground,"BOOL_OP,OR,COMPOSITE_TEST,""""""1"""""",TEST_CLAUSE,TEST @Value(_normal_z) > 0",Roof
    Ground -> CityGMLGeometrySetter
    Roof -> CityGMLGeometrySetter_3
    Wall -> CityGMLGeometrySetter_4
CityGMLGeometrySetter
    GEOM = lod2MultiSurface
    ROLE = boundedBy
    -> AttributeCreator_3
GroundSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
CityGMLGeometrySetter_3
    GEOM = lod2MultiSurface
    ROLE = boundedBy
    -> AttributeCreator_2
RoofSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
CityGMLGeometrySetter_4
    GEOM = lod2MultiSurface
    ROLE = boundedBy
    -> AttributeCreator_4
WallSurface (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_level_of_detail{} xml_buffer, citygml_opening{}.xlink_href xml_buffer
Aggregator
    ACCUM_ATTRS_NAME = Use Attributes From One Feature
    AGGREGATE_TYPE = Homogeneous Collection (If Possible)
    GROUP_BY = build_id
    MODE = Geometry - Assemble One Level
    SEP = ,

Bookmark: Read shp file
campus_inffeld_basis (reader SHAPEFILE_1)
    attributes: _mean double, _median double, yoc short, st_above long, address_bp char(20), bp_id long
    -> Extruder

Bookmark: extrude height -> 3D
Extruder
    DIRECTION = Vertical
    DISTANCE = @Value(_median)
    EXTRUDED -> GeometryRemover
    EXTRUDED -> GeometryCoercer

Bookmark: remove geometry from building
GeometryRemover
    -> CityGMLGeometrySetter_5

Bookmark: set CityGML Geometry LoD2
CityGMLGeometrySetter_5
    GEOM = lod2MultiSurface
    ROLE = cityObjectMember
    -> AttributeCreator_6

Bookmark: assign gml_parent_id
AttributeCreator_6
    ATTR_TABLE = SET_TO gml_id = @Value(bp_id)
    -> Building (writer CITYGML_1)

Bookmark: write building to CityGML file
Building (writer CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_appearance{}.xlink_href xml_buffer, citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer,
      citygml_storey_heights_above_ground_units xml_buffer, citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, gml_id00 xml_buffer

Bookmark: assign gml_parent_id
AttributeCreator_3
    ATTR_TABLE = SET_TO gml_parent_id = @Value(bp_id)
    -> GroundSurface (writer CITYGML_1)
AttributeCreator_2
    ATTR_TABLE = SET_TO gml_parent_id = @Value(bp_id)
    -> RoofSurface (writer CITYGML_1)
AttributeCreator_4
    ATTR_TABLE = SET_TO gml_parent_id = @Value(bp_id)
    -> WallSurface (writer CITYGML_1)
